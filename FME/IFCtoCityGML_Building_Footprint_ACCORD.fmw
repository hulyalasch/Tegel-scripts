FME workspace IFCtoCityGML_Building_Footprint_ACCORD.fmw

Parameters:
- SourceDataset_IFC = X:\Source\Project.ifc   # Source Industry Foundation Class (IFC) File(s)
- DestDataset_CITYGML = X:\Source\Building_Footprint.gml   # Destination CityGML Document
- OutputFolder = G:\AG_GDI-HH\ACCORD\Beispieldaten Tegel Projekt\IFC\20240702_RevitModelleundIFC\2024-06-14-UC1 and UC2 - IFC 2x3 und IFC 4\test   # Select an output folder

Readers:
- IFC_1: IFC from $(SourceDataset_IFC) in EPSG:3068

Writers:
- CITYGML_2: CITYGML to $(DestDataset_CITYGML) in EPSG:25833

Note: To run this workspace, please download and extract the DCR-LOD_100.zip from the Vectorworks Website / The IFC Reader uses the DC_Riverside_Bldg-LOD_100.ifc file
IfcSpace (reader IFC_1)
    attributes: GlobalId char(22), Name string, Description string, ObjectType string, LongName string, CompositionType enumeration, InteriorOrExteriorSpace enumeration, ElevationWithFlooring real, VW Design geometry
    -> Triangulator
Note: Set Rejected Feature Handling to Continue / To do this, right-click on the <Rejected> port, then expand Workspace: Rejected Feature Handling and then select Continue.
Triangulator
    DEAGGREGATE_INPUT = Deaggregate
    TIN_SURFACE -> MeshMerger
MeshMerger
    ACCUM_INPUT_ATTRS = Use Attributes From One Feature
    MESH -> CityGMLGeometrySetter
Building (writer CITYGML_2)
    attributes: gml_name xml_char(200), citygml_feature_role xml_char(200), GlobalId xml_char(22), Name xml_buffer, Description xml_buffer, ObjectType xml_buffer, LongName xml_buffer, CompositionType xml_buffer, InteriorOrExteriorSpace xml_buffer, ElevationWithFlooring xml_real64, VW Design xml_buffer, ifc_parent_unique_id xml_buffer, ifc_unique_id xml_buffer, ifc_parent_id xml_buffer

Bookmark: Set CityGML specific attributes
CityGMLGeometrySetter
    GEOM = lod2Solid
    ROLE = cityObjectMember
    -> AttributeCreator
AttributeCreator
    ATTR_TABLE:
      SET_TO citygml_level_of_detail = 2
      SET_TO gml_id = gml_@UUID()
      SET_TO gml_name = dc_riverside_building
    -> Scaler

Bookmark: Scale and set coordinate system
Scaler
    RASTER_SCALING = Extents
    SCALE_ORIGIN = 0,0
    TEXT_LOC_ONLY = Location and Size
    XSCALE = 1
    YSCALE = 1
    ZSCALE = 1
    SCALED -> LocalCoordinateSystemSetter
LocalCoordinateSystemSetter
    ORIGIN_CS = EPSG:3068
    ORIGIN_X = -76.986560155564575
    ORIGIN_Y = 38.876070469421258
    PROJECTION_TYPE = Equidistant (AZMED)
    PROJECTION_UNITS = Meters
    -> CsmapReprojector
CsmapReprojector
    DEST = EPSG:25833
    INTERPOLATION_TYPE_NAME = Nearest Neighbor
    RASTER_CELL_SIZE = Preserve Cells
    RASTER_TOLERANCE = 0.0
    SOURCE = EPSG:3068
    VERTICAL_HANDLING = Heights are relative to the ellipsoid(s) or geocentric
    REPROJECTED -> Building (writer CITYGML_2)

FME custom transformer CityGMLGeometrySetter
This transformer provides a convenient way to set both the CityGML LOD Name and role from a preset list of options.
Input Ports
    Input
    Features to tag with City LOD name and feature role 
    Output Ports
    Output
    Features tagged with City LOD name and feature role 
    Parameters
    CityGML Lod Name
    Select the desired CityGML Lod name
    Feature Role
    Select the desired feature role

Parameters:
- GEOM =   # CityGML Lod Name
- ROLE =   # Feature Role

Input (input)
    -> AttributeCreator
Note: Set LOD name / and citygml role
AttributeCreator
    ATTR_TABLE:
      SET_TO citygml_lod_name = $(GEOM)
      SET_TO citygml_feature_role = $(ROLE)
    -> GeometryPropertySetter
Note: Convert LOD to geometry trait
GeometryPropertySetter
    GQUERY:
      for $geom in //geometry
      where $geom/count(parent::geometry) = 0
      return number($geom/@fme_id)
    OVERWRITE_CHOICE = Yes
    REMOVE_ATTRIBUTE = No
    SETTYPE_PARAM = Traits From Attributes
    SRC_ATTRS = citygml_lod_name
    SET -> Output (output)
Output (output)
